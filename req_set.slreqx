# req_set

## #1: Входное значение (Functional)
Управляющий сигнал поющего фонтана.

## #2: Выходное значение (Functional)
На выходе получаем высоту струи воды из сопла фонтана.

## #3: Сила струи (Functional)
Функция расчёта силы струи воды на выходе из сопла фонтана.

## #4: Системная константа (Functional)
Константа содержит значение силы тяжести, рассчитанное для объекта массой 500кг.

## #5: Линия обратной связи (Functional)
Линия обратной связи для сумматора.

## #6: PID регулятор (Functional)

## #7: Функция вычисления мощности (Functional)

## #8: Имитация подвесного ящика (Functional)
Необходимо для вычисления высоты струи воды из сопла фонтана.

## #9: Генератор (Functional)
Генератор входных значений

## #10: Шина данных (Functional)
